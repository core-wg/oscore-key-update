module ietf-schc-coap-kudos {
  yang-version 1.1;
  namespace "urn:ietf:params:xml:ns:yang:ietf-schc-coap-kudos";
  prefix schc-coap-kudos;

  import ietf-schc {
      prefix schc;
  }

  organization
    "IETF CORE (Constrained RESTful Environments) Working Group";
  contact
    "WG Web:   https://datatracker.ietf.org/wg/core
     WG List:  CORE <mailto:core@ietf.org>
     Editor:   Marco Tiloca
               <mailto:marco.tiloca@ri.se>";
  description
    "This module extends the ietf-schc module defined in RFC 9363 to
     include the extended format of the CoAP OSCORE Option for using
     Key Update for OSCORE (KUDOS), as defined in RFC XXXX.

     Copyright (c) 2026 IETF Trust and the persons identified
     as authors of the code.  All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     All revisions of IETF and IANA published modules can be found
     at the YANG Parameters registry group
     (https://www.iana.org/assignments/yang-parameters).

     This version of this YANG module is part of RFC XXXX; see
     the RFC itself for full legal notices.";

  revision 2026-07-06 {
    description
      "Extended OSCORE fields for Key Update for OSCORE (KUDOS).";
    reference
      "RFC XXXX Key Update for OSCORE (KUDOS)
                (see Sections 4.1 and 5)";
  }

  // Field ID

  identity fid-coap-option-oscore-x {
       base "schc:fid-coap-option";
       description
         "CoAP option OSCORE x field.";
       reference
         "RFC XXXX Key Update for OSCORE (KUDOS)
                   (see Sections 4.1 and 5)";
  }

  identity fid-coap-option-oscore-nonce {
       base "schc:fid-coap-option";
       description
         "CoAP option OSCORE nonce field.";
       reference
         "RFC XXXX Key Update for OSCORE (KUDOS)
                   (see Sections 4.1 and 5)";
  }

  // Function Length

  identity fl-oscore-nonce-length {
       base "schc:fl-base-type";
       description
         "Size in bytes of the OSCORE nonce, equal to m+1.";
       reference
         "RFC XXXX Key Update for OSCORE (KUDOS) (see Section 5)";
  }
}
